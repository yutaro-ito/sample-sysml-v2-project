package 'EACS System Definition'
{
    // ====================================
    // Definition of Systems
    // ====================================
    part def EACS;
    part def External_Environment;
    part def External_System;
}
