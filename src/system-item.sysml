package 'EACS Item'
{
    // ====================================
    // Definition of Item
    // ====================================
    item def Item_External_Acceleration :> ScalarValues::Integer;
    item def Item_External_Temperature :> ScalarValues::Integer;
    item def Item_Captured_Acceleration :> ScalarValues::Integer;
    item def Item_Captured_Temperature :> ScalarValues::Integer;
    item def Item_Alert_Signal :> ScalarValues::Boolean;
}
